# FreeCAD Macro: Method 1 Reaction Torque Cradle for ILM-E85X30
# Import actual motor STEP file and create professional cradle mount test stand

import FreeCAD as App
import Part
import os

# Path to the ILM-E85X30 STEP file (adjust as needed)
MOTOR_STEP_PATH = "/Users/cyin/project/robot/MotorTestSandBox/DeviceUnderTest/ILM-E85X30 SERVO KIT PCB INFO REV.0100.step"

# Design Parameters
PARAMETERS = {
    'base_length': 800.0,
    'base_width': 600.0,
    'base_height': 40.0,
    'motor_mount_height': 150.0,
    'cradle_arm_length': 400.0,
    'pedestal_height': 120.0,
    'pedestal_width': 100.0,
    'pedestal_depth': 80.0,
    'torque_arm_length': 300.0,
    'torque_arm_width': 30.0,
    'motor_stator_diameter': 85.0,
    'motor_stator_length': 44.4,
}

def create_base_platform():
    """Create reinforced base platform"""
    base = doc.addObject("Part::Box", "BasePlatform")
    base.Length = PARAMETERS['base_length']
    base.Width = PARAMETERS['base_width']
    base.Height = PARAMETERS['base_height']
    base.Placement = App.Placement(
        App.Vector(-PARAMETERS['base_length']/2, -PARAMETERS['base_width']/2, 0),
        App.Rotation(0, 0, 0, 1)
    )
    return base

def import_motor():
    """Import ILM-E85X30 STEP file or create placeholder"""
    try:
        if os.path.exists(MOTOR_STEP_PATH):
            import Import
            Import.insert(MOTOR_STEP_PATH, doc.Name)
            doc.recompute()
            
            # Find imported objects
            imported = [obj for obj in doc.Objects if 'ILM' in obj.Label or '330816' in obj.Label]
            if imported:
                motor_compound = doc.addObject("Part::Compound", "ILM_E85X30_Motor")
                motor_compound.Links = imported
                motor_compound.Placement = App.Placement(
                    App.Vector(0, 0, PARAMETERS['motor_mount_height']),
                    App.Rotation(App.Vector(1,0,0), 90)
                )
                return motor_compound
    except:
        pass
    
    # Create placeholder if import fails
    stator = doc.addObject("Part::Cylinder", "MotorStator_Placeholder")
    stator.Radius = PARAMETERS['motor_stator_diameter'] / 2
    stator.Height = PARAMETERS['motor_stator_length']
    stator.Placement = App.Placement(
        App.Vector(0, 0, PARAMETERS['motor_mount_height']),
        App.Rotation(App.Vector(1,0,0), 90)
    )
    return stator

def create_cradle_pedestals():
    """Create trunnion bearing pedestals"""
    pedestals = []
    
    # Left pedestal
    left = doc.addObject("Part::Box", "LeftPedestal")
    left.Length = PARAMETERS['pedestal_width']
    left.Width = PARAMETERS['pedestal_depth']
    left.Height = PARAMETERS['pedestal_height']
    left.Placement = App.Placement(
        App.Vector(-PARAMETERS['cradle_arm_length']/2 - PARAMETERS['pedestal_width']/2,
                  -PARAMETERS['pedestal_depth']/2,
                  PARAMETERS['base_height']),
        App.Rotation(0, 0, 0, 1)
    )
    pedestals.append(left)
    
    # Right pedestal
    right = doc.addObject("Part::Box", "RightPedestal")
    right.Length = PARAMETERS['pedestal_width']
    right.Width = PARAMETERS['pedestal_depth']
    right.Height = PARAMETERS['pedestal_height']
    right.Placement = App.Placement(
        App.Vector(PARAMETERS['cradle_arm_length']/2 - PARAMETERS['pedestal_width']/2,
                  -PARAMETERS['pedestal_depth']/2,
                  PARAMETERS['base_height']),
        App.Rotation(0, 0, 0, 1)
    )
    pedestals.append(right)
    
    return pedestals

def create_torque_arm():
    """Create torque measurement arm"""
    arm = doc.addObject("Part::Box", "TorqueArm")
    arm.Length = PARAMETERS['torque_arm_length']
    arm.Width = PARAMETERS['torque_arm_width']
    arm.Height = 10
    arm.Placement = App.Placement(
        App.Vector(0, -PARAMETERS['torque_arm_width']/2,
                  PARAMETERS['motor_mount_height'] + PARAMETERS['motor_stator_diameter']/2 + 20),
        App.Rotation(0, 0, 0, 1)
    )
    
    # Load cell at end
    load_cell = doc.addObject("Part::Cylinder", "LoadCell")
    load_cell.Radius = 12.5
    load_cell.Height = 50
    load_cell.Placement = App.Placement(
        App.Vector(PARAMETERS['torque_arm_length']/2, 0,
                  PARAMETERS['motor_mount_height'] + PARAMETERS['motor_stator_diameter']/2 + 30),
        App.Rotation(0, 0, 0, 1)
    )
    
    return [arm, load_cell]

def apply_colors():
    """Apply professional colors"""
    colors = {
        'BasePlatform': (0.5, 0.5, 0.5),      # Gray base
        'Motor': (0.2, 0.3, 0.8),             # Blue motor  
        'Pedestal': (0.8, 0.8, 0.9),          # Light blue pedestals
        'TorqueArm': (0.9, 0.7, 0.1),         # Yellow arm
        'LoadCell': (0.8, 0.1, 0.1),          # Red load cell
    }
    
    for obj in doc.Objects:
        if hasattr(obj, 'ViewObject'):
            for name_part, color in colors.items():
                if name_part in obj.Label:
                    obj.ViewObject.ShapeColor = color
                    break

# Main execution
doc = App.newDocument("Method1_ILM_E85X30_Cradle")

print("Creating Method 1 Reaction Torque Cradle for ILM-E85X30...")

# Create components
base = create_base_platform()
motor = import_motor()
pedestals = create_cradle_pedestals()
torque_parts = create_torque_arm()

# Apply visual styling
apply_colors()

doc.recompute()

# Fit view
try:
    App.Gui.SendMsgToActiveView("ViewFit")
except:
    pass

print("Method 1 Cradle Assembly Complete!")
print(f"Components created:")
print(f"  ✅ Base Platform: {PARAMETERS['base_length']}×{PARAMETERS['base_width']}mm")
print(f"  ✅ Motor: ILM-E85X30 (from STEP file)")
print(f"  ✅ Cradle Pedestals: {len(pedestals)} units")
print(f"  ✅ Torque Arm: {PARAMETERS['torque_arm_length']}mm length")
print(f"  ✅ Load Cell: Reaction torque measurement")
print(f"\nFormula: Torque = Force × {PARAMETERS['torque_arm_length']}mm")
