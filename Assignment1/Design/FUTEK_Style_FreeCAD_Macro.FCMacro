# FreeCAD Macro: FUTEK-Style Horizontal Motor Test Bench
# Professional Configuration: Motor → Torque Sensor → Eddy Current Brake
# Based on Example 2 reference design

import FreeCAD as App
import Part

# Design Parameters
FUTEK_PARAMETERS = {'base_length': 1000.0, 'base_width': 400.0, 'base_height': 20.0, 'base_material': 'Aluminum_6061_T6', 'base_mounting_holes': 8, 'motor_position_x': 150.0, 'motor_mount_height': 100.0, 'motor_stator_diameter': 85.0, 'motor_stator_length': 44.4, 'motor_rotor_bore': 52.0, 'motor_shaft_extension': 50.0, 'sensor_position_x': 500.0, 'sensor_type': 'FUTEK_TRS600', 'sensor_length': 100.0, 'sensor_diameter': 50.0, 'sensor_shaft_diameter': 25.0, 'sensor_range': '50_Nm', 'sensor_accuracy': 0.1, 'brake_position_x': 850.0, 'brake_disc_diameter': 200.0, 'brake_disc_thickness': 30.0, 'brake_housing_width': 150.0, 'brake_housing_height': 120.0, 'brake_fin_count': 24, 'brake_max_torque': 15.0, 'main_shaft_diameter': 25.0, 'main_shaft_length': 600.0, 'shaft_material': 'Stainless_316', 'shaft_surface_finish': 0.8, 'pedestal_count': 3, 'pedestal_height': 100.0, 'pedestal_width': 80.0, 'pedestal_depth': 120.0, 'pedestal_material': 'Aluminum_6061_T6', 'bearing_type': 'Ball_6005', 'bearing_housing_type': 'Pillow_Block', 'coupling_type': 'Flexible_Jaw', 'coupling_bore': 25.0, 'coupling_od': 65.0, 'coupling_length': 40.0, 'coupling_torque_rating': 20.0, 'daq_interface': 'USB520', 'display_type': 'IHH500', 'computer_interface': 'USB', 'sampling_rate': 1000, 'data_logging': True, 'guard_material': 'Polycarbonate', 'guard_thickness': 5.0, 'emergency_stop': True, 'interlocks': True, 'rotating_guard_coverage': '360_degree', 'motor_drive_type': 'Servo_Drive', 'motor_drive_voltage': 48.0, 'motor_drive_current': 25.0, 'brake_controller_voltage': 24.0, 'control_system': 'PLC_Based', 'torque_measurement_range': '0-50_Nm', 'speed_range': '0-3000_rpm', 'measurement_accuracy': 0.1, 'resolution': 0.01, 'bandwidth': 1000, 'operating_temp_range': '15-40_degC', 'humidity_max': 85, 'vibration_isolation': True, 'noise_level_max': 65}

def create_base_platform():
    """Create aluminum base platform"""
    doc = App.ActiveDocument
    
    base = doc.addObject("Part::Box", "BasePlatform")
    base.Length = FUTEK_PARAMETERS['base_length']
    base.Width = FUTEK_PARAMETERS['base_width'] 
    base.Height = FUTEK_PARAMETERS['base_height']
    base.Placement = App.Placement(
        App.Vector(0, -FUTEK_PARAMETERS['base_width']/2, 0),
        App.Rotation(0, 0, 0, 1)
    )
    
    return base

def create_motor_assembly():
    """Create motor assembly at left position"""
    doc = App.ActiveDocument
    
    # Motor housing (ILM-E85x30)
    motor = doc.addObject("Part::Cylinder", "MotorHousing")
    motor.Radius = FUTEK_PARAMETERS['motor_stator_diameter'] / 2
    motor.Height = FUTEK_PARAMETERS['motor_stator_length']
    motor.Placement = App.Placement(
        App.Vector(FUTEK_PARAMETERS['motor_position_x'], 0, FUTEK_PARAMETERS['motor_mount_height']),
        App.Rotation(App.Vector(0,1,0), 90)
    )
    
    return motor

def create_torque_sensor():
    """Create FUTEK TRS-style torque sensor"""
    doc = App.ActiveDocument
    
    # Sensor body (red - FUTEK style)
    sensor = doc.addObject("Part::Cylinder", "TorqueSensor")
    sensor.Radius = FUTEK_PARAMETERS['sensor_diameter'] / 2
    sensor.Height = FUTEK_PARAMETERS['sensor_length']
    sensor.Placement = App.Placement(
        App.Vector(FUTEK_PARAMETERS['sensor_position_x'], 0, FUTEK_PARAMETERS['motor_mount_height']),
        App.Rotation(App.Vector(0,1,0), 90)
    )
    
    return sensor

def create_brake_assembly():
    """Create eddy current brake with finned disc"""
    doc = App.ActiveDocument
    
    # Brake housing
    brake_housing = doc.addObject("Part::Box", "BrakeHousing")
    brake_housing.Length = FUTEK_PARAMETERS['brake_housing_width']
    brake_housing.Width = FUTEK_PARAMETERS['brake_housing_width']
    brake_housing.Height = FUTEK_PARAMETERS['brake_housing_height']
    brake_housing.Placement = App.Placement(
        App.Vector(FUTEK_PARAMETERS['brake_position_x'] - FUTEK_PARAMETERS['brake_housing_width']/2,
                  -FUTEK_PARAMETERS['brake_housing_width']/2,
                  FUTEK_PARAMETERS['motor_mount_height'] - 40),
        App.Rotation(0, 0, 0, 1)
    )
    
    # Brake disc with fins
    brake_disc = doc.addObject("Part::Cylinder", "BrakeDisc")
    brake_disc.Radius = FUTEK_PARAMETERS['brake_disc_diameter'] / 2
    brake_disc.Height = FUTEK_PARAMETERS['brake_disc_thickness']
    brake_disc.Placement = App.Placement(
        App.Vector(FUTEK_PARAMETERS['brake_position_x'], 0, FUTEK_PARAMETERS['motor_mount_height']),
        App.Rotation(App.Vector(0,1,0), 90)
    )
    
    return [brake_housing, brake_disc]

def create_main_shaft():
    """Create the main shaft connecting motor to brake"""
    doc = App.ActiveDocument
    
    shaft_start_x = FUTEK_PARAMETERS['motor_position_x'] + 100  # Approximate
    shaft_length = FUTEK_PARAMETERS['brake_position_x'] - shaft_start_x - 100
    
    shaft = doc.addObject("Part::Cylinder", "MainShaft")
    shaft.Radius = FUTEK_PARAMETERS['main_shaft_diameter'] / 2
    shaft.Height = shaft_length
    shaft.Placement = App.Placement(
        App.Vector(shaft_start_x, 0, FUTEK_PARAMETERS['motor_mount_height']),
        App.Rotation(App.Vector(0,1,0), 90)
    )
    
    return shaft

def create_bearing_pedestals():
    """Create bearing pedestals"""
    doc = App.ActiveDocument
    
    pedestals = []
    positions = [
        FUTEK_PARAMETERS['motor_position_x'],
        FUTEK_PARAMETERS['sensor_position_x'] - 60,
        FUTEK_PARAMETERS['sensor_position_x'] + 60,
        FUTEK_PARAMETERS['brake_position_x']
    ]
    
    for i, pos_x in enumerate(positions):
        pedestal = doc.addObject("Part::Box", f"Pedestal_{i}")
        pedestal.Length = FUTEK_PARAMETERS['pedestal_width']
        pedestal.Width = FUTEK_PARAMETERS['pedestal_depth']
        pedestal.Height = FUTEK_PARAMETERS['pedestal_height']
        pedestal.Placement = App.Placement(
            App.Vector(pos_x - FUTEK_PARAMETERS['pedestal_width']/2,
                      -FUTEK_PARAMETERS['pedestal_depth']/2,
                      FUTEK_PARAMETERS['base_height']),
            App.Rotation(0, 0, 0, 1)
        )
        pedestals.append(pedestal)
    
    return pedestals

def apply_colors(components):
    """Apply professional colors to components"""
    color_scheme = {
        'BasePlatform': (0.7, 0.7, 0.7),        # Aluminum gray
        'MotorHousing': (0.2, 0.3, 0.8),        # Blue motor
        'TorqueSensor': (0.8, 0.1, 0.1),        # FUTEK red
        'BrakeHousing': (0.3, 0.3, 0.3),        # Dark gray
        'BrakeDisc': (0.3, 0.3, 0.3),           # Dark gray
        'MainShaft': (0.9, 0.9, 0.8),           # Stainless steel
    }
    
    for obj in App.ActiveDocument.Objects:
        if obj.Name.startswith('Pedestal'):
            obj.ViewObject.ShapeColor = (0.8, 0.8, 0.9)  # Light aluminum
        elif obj.Name in color_scheme:
            obj.ViewObject.ShapeColor = color_scheme[obj.Name]

def generate_futek_assembly():
    """Generate complete FUTEK-style assembly"""
    # Create new document
    doc = App.newDocument("FUTEK_MotorTestBench")
    
    print("Creating FUTEK-Style Horizontal Motor Test Bench...")
    
    # Create all components
    base = create_base_platform()
    motor = create_motor_assembly()
    sensor = create_torque_sensor()
    brake_parts = create_brake_assembly()
    shaft = create_main_shaft()
    pedestals = create_bearing_pedestals()
    
    # Apply colors
    apply_colors([base, motor, sensor] + brake_parts + [shaft] + pedestals)
    
    doc.recompute()
    
    # Fit view
    try:
        App.Gui.SendMsgToActiveView("ViewFit")
    except:
        pass
    
    print("Assembly Complete!")
    print(f"Total Length: {FUTEK_PARAMETERS['base_length']} mm")
    print(f"Motor Position: {FUTEK_PARAMETERS['motor_position_x']} mm")
    print(f"Sensor Position: {FUTEK_PARAMETERS['sensor_position_x']} mm")
    print(f"Brake Position: {FUTEK_PARAMETERS['brake_position_x']} mm")
    
    return doc

# Execute the assembly
if __name__ == "__main__":
    generate_futek_assembly()
